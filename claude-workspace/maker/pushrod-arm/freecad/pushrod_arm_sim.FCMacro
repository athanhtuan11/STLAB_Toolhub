# -*- coding: utf-8 -*-
# Mo phong canh tay robot push-rod CyberBrick (pushrod_arm.FCStd)
# Chay: Macro > Macros... > pushrod_arm_sim.FCMacro > Execute
# 4 khop: xoay de, xi-lanh vai, xi-lanh khuyu, kep. Tu the goc luu trong pushrod_arm_rest.json
import FreeCAD as App, FreeCADGui as Gui, math, json, os
from FreeCAD import Vector as V
try:
    from PySide import QtCore, QtGui
    QtW = QtGui
    QtW.QWidget
except Exception:
    from PySide2 import QtCore, QtWidgets as QtW

DOC = App.getDocument("pushrod_arm")
REST_FILE = os.path.join(os.path.dirname(DOC.FileName), "pushrod_arm_rest.json")  # canh file .FCStd
REST = {n: App.Placement(V(*b), App.Rotation(*q)) for n, (b, q) in json.load(open(REST_FILE)).items()}
OBJ = {o.Label: o for o in DOC.Objects if o.isDerivedFrom("Part::Feature")}

def along(p, a, d): return (p[0] + d*math.cos(math.radians(a)), p[1] + d*math.sin(math.radians(a)))
def offs(p, a, d): return (p[0] - d*math.sin(math.radians(a)), p[1] + d*math.cos(math.radians(a)))
DZ = 4
S0 = (0, 80); E0 = (96.41814145600076, 194.90666646784498)
def g(p): return V(p[0], 0, p[1] + DZ)
S = g(S0); A = g((20, 52)); E = g(E0)
B = g(offs(along(S0, 50, 90), 50, -18)); C = g(offs(along(S0, 50, 38), 50, 21)); D = g(offs(along(E0, -30, -25), -30, 14))
F0 = (E0[0] + 130*math.cos(math.radians(-30)), E0[1] + 130*math.sin(math.radians(-30)))
PG = App.Placement(V(F0[0], 0, F0[1] + DZ), App.Rotation(V(0, 1, 0), 30))
J1 = PG.multVec(V(28, 0, 7.5)); J2 = PG.multVec(V(28, 0, -7.5))
L1_0 = (B - A).Length; L2_0 = (D - C).Length
LMIN, LMAX = 92.0, 128.0      # rack rear inside housing: 16..52 mm
L1MAX = 118.0                  # vai: >118 mm (boom >90 do) xi-lanh vai dam vao boom
RP = 5.0
YAXIS = V(0, 1, 0); ZAXIS = V(0, 0, 1)
def rot(center, axis, deg): return App.Placement(V(0, 0, 0), App.Rotation(axis, deg), center)
def angxz(v): return math.degrees(math.atan2(v.z, v.x))
# xi-lanh piston (2026-10-25): he xi-lanh = Placement Piston_rod_<tag>; ty ren M3 (buoc 0,5) quay quanh truc x, z28 o z = zs*20
SCREW_C = {}; G28_C = {}; AX_D = {}
for tag, zs in (("Shoulder", -1), ("Elbow", 1)):
    F_ = REST[OBJ["Piston_rod_" + tag].Name]
    SCREW_C[tag] = F_.multVec(V(0, 0, 0)); G28_C[tag] = F_.multVec(V(0, 0, zs*20.0))
    AX_D[tag] = F_.Rotation.multVec(V(1, 0, 0))
def screw_deg(dL): return dL/0.5*360.0          # do quay ty ren theo do dai xi-lanh doi (mm)

BASE_FIXED = {"Base_housing", "Base_foot", "Base_deck", "Slide_ring", "CB_Servo9g_360_turntable",
              "Pinion_m1_z10_turntable", "CB_XA003_XA004_receiver", "Receiver_riser", "Battery_bay"}
def grp(label):
    gg = [o for o in DOC.Objects if o.Label == label]
    out = []
    def walk(x):
        for o in x.Group:
            if o.isDerivedFrom("App::DocumentObjectGroup"): walk(o)
            else: out.append(o.Label)
    if gg: walk(gg[0])
    return out
BOOM = set(["Boom001"] + [l for l in OBJ if l.startswith(("Pin_B", "Pin_C", "Pin_E"))])
FORE = set(grp("Forearm") + grp("Gripper") + [l for l in OBJ if l.startswith("Pin_D")])
JAW1 = {"Jaw_1_driven_by_servo", "Jaw_1_driven_by_servo_TPU_pad", "Servo_horn"}
JAW2 = {"Jaw_2_idler", "Jaw_2_idler_TPU_pad"}
ROD1 = set(grp("PushRod_Shoulder")); ROD2 = set(grp("PushRod_Elbow"))

def solve(fun, lo, hi):
    # find angle with fun(angle)=0, scan then bisect
    prev = None; a = lo
    while a <= hi:
        v = fun(a)
        if prev is not None and (v == 0 or (v > 0) != (prev[1] > 0)):
            x0, x1 = prev[0], a
            for _ in range(40):
                m = (x0 + x1)/2
                if (fun(m) > 0) == (fun(x0) > 0): x0 = m
                else: x1 = m
            return (x0 + x1)/2
        prev = (a, v); a += 0.5
    return None

STATE = {"yaw": 0.0, "L1": L1_0, "L2": L2_0, "grip": 0.0}
def set_pose(yaw=None, L1=None, L2=None, grip=None, update=True):
    s = STATE
    if yaw is not None: s["yaw"] = max(-170, min(170, yaw))
    if L1 is not None: s["L1"] = max(LMIN, min(L1MAX, L1))
    if L2 is not None: s["L2"] = max(LMIN, min(LMAX, L2))
    if grip is not None: s["grip"] = max(-55, min(3, grip))
    # shoulder: boom angle from rod 1 length
    phi = solve(lambda a: (rot(S, YAXIS, a).multVec(B) - A).Length - s["L1"], -80, 80)
    if phi is None: return False
    Mb = rot(S, YAXIS, phi)
    C1 = Mb.multVec(C); E1 = Mb.multVec(E); D_b = Mb.multVec(D)
    psi = solve(lambda a: (rot(E1, YAXIS, a).multVec(D_b) - C1).Length - s["L2"], -120, 120)
    if psi is None: return False
    Mf = rot(E1, YAXIS, psi).multiply(Mb)
    D1 = Mf.multVec(D); B1 = Mb.multVec(B)
    # rods
    d1 = -(angxz(B1 - A) - angxz(B - A)); Mr1 = rot(A, YAXIS, d1)
    dB = Mb.Rotation.multVec(D - C)
    d2 = -(angxz(D1 - C1) - angxz(dB)); Mr2 = rot(C1, YAXIS, d2).multiply(Mb)
    u1 = (B1 - A); u1.normalize(); u2 = (D1 - C1); u2.normalize()
    T1 = App.Placement(u1*(s["L1"] - L1_0), App.Rotation()); T2 = App.Placement(u2*(s["L2"] - L2_0), App.Rotation())
    Y = rot(V(0, 0, 0), ZAXIS, s["yaw"])
    for lbl, o in OBJ.items():
        R = REST.get(o.Name)
        if R is None: continue
        if lbl in BASE_FIXED or lbl.startswith(("M2_5x6_deck", "M2_5x8_deck")):
            M = App.Placement()
            if lbl == "Pinion_m1_z10_turntable": M = rot(V(35, 0, 0), ZAXIS, -6*s["yaw"])
        else:
            if lbl in BOOM: M = Mb
            elif lbl in FORE:
                M = Mf
                if lbl in JAW1: M = Mf.multiply(rot(J1, YAXIS, s["grip"]))
                elif lbl in JAW2: M = Mf.multiply(rot(J2, YAXIS, -s["grip"]))
            elif lbl in ROD1:
                M = Mr1
                if lbl.startswith(("Piston_rod", "LK_Nut_M3_piston")): M = T1.multiply(Mr1)
                elif lbl.startswith(("Gear_z12", "LK_Threaded_rod", "LK_Nut_M3_gear")): M = Mr1.multiply(rot(SCREW_C["Shoulder"], AX_D["Shoulder"], screw_deg(s["L1"] - L1_0)))
                elif lbl.startswith("Gear_z28"): M = Mr1.multiply(rot(G28_C["Shoulder"], AX_D["Shoulder"], -12/28*screw_deg(s["L1"] - L1_0)))
            elif lbl in ROD2:
                M = Mr2
                if lbl.startswith(("Piston_rod", "LK_Nut_M3_piston")): M = T2.multiply(Mr2)
                elif lbl.startswith(("Gear_z12", "LK_Threaded_rod", "LK_Nut_M3_gear")): M = Mr2.multiply(rot(SCREW_C["Elbow"], AX_D["Elbow"], screw_deg(s["L2"] - L2_0)))
                elif lbl.startswith("Gear_z28"): M = Mr2.multiply(rot(G28_C["Elbow"], AX_D["Elbow"], -12/28*screw_deg(s["L2"] - L2_0)))
            else: M = App.Placement()
            M = Y.multiply(M)
        o.Placement = M.multiply(R)
    s["phi"], s["psi"] = phi, psi
    if update: Gui.updateGui()
    return True

def reset(): set_pose(0, L1_0, L2_0, 0)

COLL_SETS = {"ROD1": ["Housing_Shoulder", "Piston_rod_Shoulder", "CB_030_gearbox_Shoulder", "Gear_z28_Shoulder", "Gear_z12_Shoulder"],
             "ROD2": ["Housing_Elbow", "Piston_rod_Elbow", "CB_030_gearbox_Elbow", "Gear_z28_Elbow", "Gear_z12_Elbow"],
             "BOOM": ["Boom001"],
             "FORE": ["Forearm_plate_L", "Forearm_plate_R", "Gripper_frame", "CB_Servo9g_180_gripper", "Jaw_1_driven_by_servo", "Jaw_2_idler", "Gripper_top_plate", "Spacer_D", "Wrist_spacer"],
             "TUR": ["Turret_one_piece", "Spacer_S", "Spacer_S001", "Spacer_A", "Spacer_A001"],
             "BASE": ["Base_housing", "Base_deck", "Turntable"]}
COLL_PAIRS = [("ROD1", "BOOM"), ("ROD1", "TUR"), ("ROD1", "ROD2"), ("ROD1", "FORE"), ("ROD2", "BOOM"), ("ROD2", "FORE"),
              ("FORE", "BOOM"), ("FORE", "TUR"), ("FORE", "BASE"), ("BOOM", "TUR"), ("BOOM", "BASE"), ("ROD2", "TUR")]
# trong xi-lanh piston: ty truot trong vo, khong cham banh rang/vo
INNER = [("Piston_rod_%s", "Housing_%s"), ("Piston_rod_%s", "Gear_z12_%s"), ("Gear_z28_%s", "Housing_%s"), ("Gear_z12_%s", "Housing_%s")]
def coll_pairs():
    out = [(na, nb) for a, b in COLL_PAIRS for na in COLL_SETS[a] for nb in COLL_SETS[b] if na in OBJ and nb in OBJ]
    return out + [(a % t, b % t) for t in ("Shoulder", "Elbow") for a, b in INNER if a % t in OBJ and b % t in OBJ]

FAST = {}
def fast_collider():
    # chia luoi 1 lan moi phien macro (sua model -> chay lai macro); thieu manifold3d -> None (dung B-rep)
    if "c" not in FAST:
        try:
            import sys
            sys.path.insert(0, os.path.join(os.path.dirname(REST_FILE), "..", "..", "..", "tools", "robotics-cad", "scripts"))
            import fast_collide
            FAST["c"] = fast_collide.Collider({l: OBJ[l] for p in coll_pairs() for l in p})
        except Exception as e:
            App.Console.PrintWarning("fast_collide khong dung duoc (%s) -> B-rep\n" % e); FAST["c"] = None
    return FAST["c"]

def check_collisions(fast=None):
    # fast = robotics-cad/scripts/fast_collide.Collider (luoi, ~ms/cap); khong co -> boolean B-rep (~3 s/tu the)
    if fast is not None:
        return fast.hits(coll_pairs())
    hits = []
    for na, nb in coll_pairs():
        sa, sb = OBJ[na].Shape, OBJ[nb].Shape
        bb = sa.BoundBox; bb.enlarge(0.5)
        if not bb.intersect(sb.BoundBox): continue
        try: v = sa.common(sb).Volume
        except Exception: continue
        if v > 0.5: hits.append("%s x %s: %.1f mm3" % (na, nb, v))
    return hits

class Panel(QtW.QWidget):
    def __init__(self):
        super().__init__()
        self.setWindowTitle("Mo phong canh tay")
        lay = QtW.QVBoxLayout(self)
        self.sl = {}
        for key, txt, lo, hi, val, sc in (("yaw", "Xoay de (do)", -170, 170, 0, 1),
                                         ("L1", "Xi-lanh vai (mm)", LMIN, L1MAX, L1_0, 10),
                                         ("L2", "Xi-lanh khuyu (mm)", LMIN, LMAX, L2_0, 10),
                                         ("grip", "Kep: -55 mo / +3 kep (do)", -55, 3, 0, 1)):
            lb = QtW.QLabel(); s = QtW.QSlider(QtCore.Qt.Horizontal)
            s.setRange(int(lo*sc), int(hi*sc)); s.setValue(int(val*sc))
            s.valueChanged.connect(lambda v, k=key, c=sc: self.change(k, v/c))
            lay.addWidget(lb); lay.addWidget(s); self.sl[key] = (s, lb, txt, sc)
        self.info = QtW.QLabel(); lay.addWidget(self.info)
        row = QtW.QHBoxLayout()
        for t, f in (("Demo", self.demo), ("Ve goc", self.reset), ("Kiem tra va cham", self.check)):
            b = QtW.QPushButton(t); b.clicked.connect(f); row.addWidget(b)
        lay.addLayout(row)
        self.out = QtW.QLabel(""); self.out.setWordWrap(True); lay.addWidget(self.out)
        self.timer = QtCore.QTimer(); self.timer.timeout.connect(self.step); self.t = 0
        self.refresh()
    def change(self, k, v):
        if not set_pose(**{k: v}): self.out.setText("Ngoai tam dong hoc")
        self.refresh()
    def refresh(self):
        for k, (s, lb, txt, sc) in self.sl.items(): lb.setText("%s: %.1f" % (txt, STATE[k]))
        self.info.setText("Hanh trinh vai %.1f/36 mm, khuyu %.1f/36 mm | goc boom %+.1f, forearm %+.1f" % (
            STATE["L1"] - LMIN, STATE["L2"] - LMIN, -STATE.get("phi", 0), -STATE.get("psi", 0)))
    def sync(self):
        for k, (s, lb, txt, sc) in self.sl.items():
            s.blockSignals(True); s.setValue(int(STATE[k]*sc)); s.blockSignals(False)
        self.refresh()
    def reset(self):
        self.timer.stop(); reset(); self.sync(); self.out.setText("")
    def demo(self):
        if self.timer.isActive(): self.timer.stop(); return
        self.t = 0; self.timer.start(40)
    def step(self):
        self.t += 1; t = self.t/50.0
        mid = (LMIN + LMAX)/2; amp = (LMAX - LMIN)/2*0.9
        set_pose(yaw=120*math.sin(t*0.6), L1=(LMIN+L1MAX)/2 + (L1MAX-LMIN)/2*0.9*math.sin(t), L2=mid + amp*math.sin(t*1.3 + 1), grip=-26 + 29*math.sin(t*2))
        self.sync()
        if self.t > 50*12: self.timer.stop()
    def check(self):
        self.out.setText("Dang kiem tra..."); Gui.updateGui()
        h = check_collisions(fast_collider())
        self.out.setText("Khong va cham" if not h else "VA CHAM:\n" + "\n".join(h))

mw = Gui.getMainWindow()
for d in mw.findChildren(QtW.QDockWidget):
    if d.objectName() == "PushRodSim": d.close(); d.deleteLater()
dock = QtW.QDockWidget("Mo phong push-rod arm", mw); dock.setObjectName("PushRodSim")
PANEL = Panel(); dock.setWidget(PANEL)
mw.addDockWidget(QtCore.Qt.RightDockWidgetArea, dock)
reset()
